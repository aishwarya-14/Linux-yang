module listkey{
namespace "urn:yang:listkey";
prefix lky;
leaf first{
type uint16;
}
list detailsofemployee{
key name;
leaf name{
type string;}
leaf empid{
type uint64;
}
leaf designation
{
type string;
}
}
}
